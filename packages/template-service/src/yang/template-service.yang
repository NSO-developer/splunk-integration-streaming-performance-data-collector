module template-service {
  namespace "http://com/example/templateservice";
  prefix template-service;

  import tailf-ncs {
    prefix ncs;
  }

  container test-container {
    list test-list {
      ordered-by user;
      key test-key;
      leaf test-key {
        type string;
      }
    }
  }

  list template-service {
    description "This is an RFS skeleton service";

    key name;
    leaf name {
      type string;
    }

    uses ncs:service-data;
    ncs:servicepoint template-service-servicepoint;


    leaf max-length {
      type uint32;
    }

  }
}
